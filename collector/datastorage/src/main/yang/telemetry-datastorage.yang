module telemetry-datastorage {
    yang-version 1.1;
    namespace "urn:opendaylight:telemetry:datastorage";
    prefix "telemetry-datastorage";
    organization "ZTE corporation";
    contact "ding.rui@zte.com.cn";

    revision "2018-03-26" {
        description "Initial revision.";
    }

    grouping telemetry-data-model {
        leaf node-id {
            type string;
        }

        list telemetry-data {
            leaf timestamp {
                type uint64;
            }

            leaf base-path {
                type string;
            }

            leaf sample-interval {
                type uint64;
            }

            list key-value {
                leaf key {
                    type string;
                }

                leaf value {
                    type union {
                        type string;
                        type int64;
                        type uint64;
                        //type uint32; yangtool bug
                        //type int32; yangtool bug
                    }
                }
            }
        }
    }

    rpc data-store {
        input {
            uses telemetry-data-model;
        }
    }
}
